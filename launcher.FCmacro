import FreeCAD
from FreeCAD import Base
import math, collections
from PySide import QtGui, QtCore
import FreeCADGui

import sys
sys.path.append('D:\Dropbox\src\Python')
execfile('D:\Dropbox\src\Python\conCAD\main.py')
FreeCADGui.SendMsgToActiveView("ViewFit")
